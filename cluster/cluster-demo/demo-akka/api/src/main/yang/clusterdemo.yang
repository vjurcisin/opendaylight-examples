module clusterdemo {
    yang-version 1;
    namespace "urn:opendaylight:params:xml:ns:yang:clusterdemo";
    prefix "clusterdemo";

    revision "2015-01-05" {
        description "Initial revision of clusterdemo model";
    }
}
